MISTLAB-MIB DEFINITIONS ::= BEGIN
IMPORTS
    Integer32, IpAddress, MODULE-IDENTITY, OBJECT-TYPE, enterprises 
        FROM SNMPv2-SMI
    DisplayString
        FROM SNMPv2-TC
;


--**********************************************************************
-- Main Descritpion
--**********************************************************************
mistLab MODULE-IDENTITY
    LAST-UPDATED "202204140000Z"
    ORGANIZATION "Mist-Lab FR"
    CONTACT-INFO
        "Mist-Lab FR

        EMail: tmunzer@juniper.net"

    DESCRIPTION
        "This MIB contains definition of something
        I still have to describe..."

    REVISION
        "202204140000Z"

    DESCRIPTION
        "First revision"

    ::= { enterprises 65535 }


--**********************************************************************
-- ORG STRUCTURE
--**********************************************************************
organization OBJECT IDENTIFIER ::= { mistLab 1 }

orgName OBJECT-TYPE
    SYNTAX OCTET STRING
    MAX-ACCESS read-only
    STATUS    current
    DESCRIPTION
        "The Mist Organization Name"
    ::= { organization 1 }

orgId OBJECT-TYPE
    SYNTAX OCTET STRING
    MAX-ACCESS read-only
    STATUS    current
    DESCRIPTION
        "The Mist Organization ID"
    ::= { organization 2 }

orgStats OBJECT IDENTIFIER ::= { organization 3 }

numSites OBJECT-TYPE
    SYNTAX Integer32
    MAX-ACCESS read-only
    STATUS    current
    DESCRIPTION
        "Number of sites belonging to the org"
    ::= { orgStats 1 }


numDevices OBJECT-TYPE
    SYNTAX Integer32
    MAX-ACCESS read-only
    STATUS    current
    DESCRIPTION
        "Number of devices in the org assigned to a site"
    ::= { orgStats 2 }

numInventory OBJECT-TYPE
    SYNTAX Integer32
    MAX-ACCESS read-only
    STATUS    current
    DESCRIPTION
        "Number of devices in the org inventory"
    ::= { orgStats 3 }

numDevicesConnected OBJECT-TYPE
    SYNTAX Integer32
    MAX-ACCESS read-only
    STATUS    current
    DESCRIPTION
        "Number of connected devices in the org"
    ::= { orgStats 4 }

numDevicesDisconnected OBJECT-TYPE
    SYNTAX Integer32
    MAX-ACCESS read-only
    STATUS    current
    DESCRIPTION
        "Number of disconnected devices in the org"
    ::= { orgStats 5 }

sleCoverageTotal OBJECT-TYPE
    SYNTAX Integer32
    MAX-ACCESS read-only
    STATUS    current
    DESCRIPTION
        "Total number of user minutes used to calculate the Coverage SLE "
    ::= { orgStats 6 }

sleCoverageOk OBJECT-TYPE
    SYNTAX Integer32
    MAX-ACCESS read-only
    STATUS    current
    DESCRIPTION
        "Number of user minutes reaching the Coverage SLE threshold"
    ::= { orgStats 7 }

sleCoveragePercent OBJECT-TYPE
    SYNTAX Integer32
    MAX-ACCESS read-only
    STATUS    current
    DESCRIPTION
        "Number of user minutes reaching the Coverage SLE threshold"
    ::= { orgStats 8 }

sleFailedToConnectTotal OBJECT-TYPE
    SYNTAX Integer32
    MAX-ACCESS read-only
    STATUS    current
    DESCRIPTION
        "Total number of user minutes used to calculate the FailedToConnect SLE "
    ::= { orgStats 9 }

sleFailedToConnectOk OBJECT-TYPE
    SYNTAX Integer32
    MAX-ACCESS read-only
    STATUS    current
    DESCRIPTION
        "Number of user minutes reaching the FailedToConnect SLE threshold"
    ::= { orgStats 10 }

sleFailedToConnectPercent OBJECT-TYPE
    SYNTAX Integer32
    MAX-ACCESS read-only
    STATUS    current
    DESCRIPTION
        "Number of user minutes reaching the FailedToConnect SLE threshold"
    ::= { orgStats 11 }

sleRoamingTotal OBJECT-TYPE
    SYNTAX Integer32
    MAX-ACCESS read-only
    STATUS    current
    DESCRIPTION
        "Total number of user minutes used to calculate the Roaming SLE "
    ::= { orgStats 12 }

sleRoamingOk OBJECT-TYPE
    SYNTAX Integer32
    MAX-ACCESS read-only
    STATUS    current
    DESCRIPTION
        "Number of user minutes reaching the Roaming SLE threshold"
    ::= { orgStats 13 }

sleRoamingPercent OBJECT-TYPE
    SYNTAX Integer32
    MAX-ACCESS read-only
    STATUS    current
    DESCRIPTION
        "Number of user minutes reaching the Roaming SLE threshold"
    ::= { orgStats 14 }

sleTimeToConnectTotal OBJECT-TYPE
    SYNTAX Integer32
    MAX-ACCESS read-only
    STATUS    current
    DESCRIPTION
        "Total number of user minutes used to calculate the TimeToConnect SLE "
    ::= { orgStats 15 }

sleTimeToConnectOk OBJECT-TYPE
    SYNTAX Integer32
    MAX-ACCESS read-only
    STATUS    current
    DESCRIPTION
        "Number of user minutes reaching the TimeToConnect SLE threshold"
    ::= { orgStats 16 }

sleTimeToConnectPercent OBJECT-TYPE
    SYNTAX Integer32
    MAX-ACCESS read-only
    STATUS    current
    DESCRIPTION
        "Number of user minutes reaching the TimeToConnect SLE threshold"
    ::= { orgStats 17 }

sleThroughputTotal OBJECT-TYPE
    SYNTAX Integer32
    MAX-ACCESS read-only
    STATUS    current
    DESCRIPTION
        "Total number of user minutes used to calculate the Throughput SLE "
    ::= { orgStats 18 }

sleThroughputOk OBJECT-TYPE
    SYNTAX Integer32
    MAX-ACCESS read-only
    STATUS    current
    DESCRIPTION
        "Number of user minutes reaching the Throughput SLE threshold"
    ::= { orgStats 19 }

sleThroughputPercent OBJECT-TYPE
    SYNTAX Integer32
    MAX-ACCESS read-only
    STATUS    current
    DESCRIPTION
        "Number of user minutes reaching the Throughput SLE threshold"
    ::= { orgStats 20 }

sleCapacityTotal OBJECT-TYPE
    SYNTAX Integer32
    MAX-ACCESS read-only
    STATUS    current
    DESCRIPTION
        "Total number of user minutes used to calculate the Capacity SLE "
    ::= { orgStats 21 }

sleCapacityOk OBJECT-TYPE
    SYNTAX Integer32
    MAX-ACCESS read-only
    STATUS    current
    DESCRIPTION
        "Number of user minutes reaching the Capacity SLE threshold"
    ::= { orgStats 22 }

sleCapacityPercent OBJECT-TYPE
    SYNTAX Integer32
    MAX-ACCESS read-only
    STATUS    current
    DESCRIPTION
        "Number of user minutes reaching the Capacity SLE threshold"
    ::= { orgStats 23 }


--**********************************************************************
-- SITE STRUCTURE
--**********************************************************************
sites   OBJECT IDENTIFIER ::= { mistLab 2 }

siteTable OBJECT-TYPE
    SYNTAX SEQUENCE OF SiteEntry
    MAX-ACCESS not-accessible
    STATUS  current
    DESCRIPTION
        "This is mist sites table"
    ::= { sites 1 }

siteEntry    OBJECT-TYPE
    SYNTAX       SiteEntry
    MAX-ACCESS   not-accessible
    STATUS       current
    DESCRIPTION  
        "This is the data structure associated to
        mist sites table"
    INDEX        { siteId }
    ::= { siteTable 1 }

SiteEntry    ::= SEQUENCE {
    siteName            OCTET STRING,
    siteCountry         OCTET STRING,
    siteAddress         OCTET STRING,
    apCount             Integer32,
    apConnected         Integer32,
    switchCount         Integer32,
    switchConnected     Integer32,
    gatewayCount        Integer32,
    gatewayConnected    Integer32,
    devicesCount        Integer32,
    devicesConnected    Integer32,
    clientsCount        Integer32
}


siteId  OBJECT-TYPE
    SYNTAX  OCTET STRING  (SIZE(1..37))
    MAX-ACCESS read-only
    STATUS    current
    DESCRIPTION
        "The Mist Site ID"
    ::= { siteEntry 1 }

siteName  OBJECT-TYPE
    SYNTAX  OCTET STRING  (SIZE(1..255))
    MAX-ACCESS read-only
    STATUS    current
    DESCRIPTION
        "The Mist Site Name"
    ::= { siteEntry 2 }

siteCountry  OBJECT-TYPE
    SYNTAX  OCTET STRING  (SIZE(1..2))
    MAX-ACCESS read-only
    STATUS    current
    DESCRIPTION
        "The Mist Site Country"
    ::= { siteEntry 3 }

siteAddress  OBJECT-TYPE
    SYNTAX  OCTET STRING  (SIZE(1..255))
    MAX-ACCESS read-only
    STATUS    current
    DESCRIPTION
        "The Mist Site Address"
    ::= { siteEntry 4 }

apCount OBJECT-TYPE
    SYNTAX    Integer32 (1..65535)
    MAX-ACCESS read-only
    STATUS current
    DESCRIPTION "Number of APs"
    ::= { siteEntry 5 }

apConnected OBJECT-TYPE
    SYNTAX    Integer32 (1..65535)
    MAX-ACCESS read-only
    STATUS current
    DESCRIPTION "Number of APs connected"
    ::= { siteEntry 6 }

switchCount OBJECT-TYPE
    SYNTAX    Integer32 (1..65535)
    MAX-ACCESS read-only
    STATUS current
    DESCRIPTION "Number of switches"
    ::= { siteEntry 7 }

switchConnected OBJECT-TYPE
    SYNTAX    Integer32 (1..65535)
    MAX-ACCESS read-only
    STATUS current
    DESCRIPTION "Number of switches connected"
    ::= { siteEntry 8 }

gatewayCount OBJECT-TYPE
    SYNTAX    Integer32 (1..65535)
    MAX-ACCESS read-only
    STATUS current
    DESCRIPTION "Number of gateways"
    ::= { siteEntry 9 }

gatewayConnected OBJECT-TYPE
    SYNTAX    Integer32 (1..65535)
    MAX-ACCESS read-only
    STATUS current
    DESCRIPTION "Number of connected gateways"
    ::= { siteEntry 10 }

devicesCount OBJECT-TYPE
    SYNTAX    Integer32 (1..65535)
    MAX-ACCESS read-only
    STATUS current
    DESCRIPTION "Number of network devices"
    ::= { siteEntry 11 }

devicesConnected OBJECT-TYPE
    SYNTAX    Integer32 (1..65535)
    MAX-ACCESS read-only
    STATUS current
    DESCRIPTION "Number of network devices connected"
    ::= { siteEntry 12 }

clientsCount OBJECT-TYPE
    SYNTAX    Integer32 (1..65535)
    MAX-ACCESS read-only
    STATUS current
    DESCRIPTION "Number of Wireless clients connected"
    ::= { siteEntry 13 }


--**********************************************************************
-- AP STATS STRUCTURE
--**********************************************************************
ap   OBJECT IDENTIFIER ::= { mistLab 3 }

apStatsTable    OBJECT-TYPE
    SYNTAX SEQUENCE OF ApStatsEntry
    MAX-ACCESS not-accessible
    STATUS    current
    DESCRIPTION
        "This is the data structure associated to
        mist access points status table"
    ::= { ap 1 }

apStatsEntry    OBJECT-TYPE
    SYNTAX    ApStatsEntry
    MAX-ACCESS not-accessible
    STATUS    current
    DESCRIPTION
        "This is the data structure associated to
        mist access points status entry"
    INDEX  { siteId,apMac }
    ::= { apStatsTable 1 }

ApStatsEntry   ::= SEQUENCE {
    apMac               OCTET STRING,
    apName              DisplayString,
    apStatus            INTEGER,
    apLastSeen          Integer32,
    apUptime            Integer32,
    apHardware          OCTET STRING,
    apHardwareRev       OCTET STRING,
    apSerial            OCTET STRING,
    apIp                IpAddress,
    apPublicIp          IpAddress,
    apClientCount       Integer32,
    apLldpSysName       OCTET STRING,
    apLldpSysDesc       OCTET STRING,
    apLldpPortId        OCTET STRING,
    apLldpPortDesc      OCTET STRING,
    apLldpChassisId     OCTET STRING,
    apLldpMed           INTEGER,
    apPwrReq            Integer32,
    apPwrAlloc          Integer32,
    apPwrDraw           Integer32
}

apMac  OBJECT-TYPE
    SYNTAX  OCTET STRING (SIZE(1..162))
    MAX-ACCESS read-only
    STATUS    current
    DESCRIPTION "Access Point MAC Address"
    ::= { apStatsEntry 1 }

apName  OBJECT-TYPE
    SYNTAX  DisplayString  (SIZE(1..255))
    MAX-ACCESS read-only
    STATUS    current
    DESCRIPTION "Access Point Name"
    ::= { apStatsEntry 2 }

apStatus  OBJECT-TYPE
    SYNTAX    INTEGER {
        disconnected (1),
        connected (2)
    }
    MAX-ACCESS read-only
    STATUS    current
    DESCRIPTION "The connection status of the AP with the Mist Cloud."
    ::= { apStatsEntry 3 }

apLastSeen OBJECT-TYPE
    SYNTAX    Integer32 (0..2147483647)
    MAX-ACCESS read-only
    STATUS current
    DESCRIPTION "The last time the Access Point contacted the Mist Cloud"
    ::= { apStatsEntry 4 }

apUptime OBJECT-TYPE
    SYNTAX    Integer32 (0..2147483647)
    MAX-ACCESS read-only
    STATUS    current
    DESCRIPTION "The Access Point Uptime"
    ::= { apStatsEntry 5 }

apHardware  OBJECT-TYPE
    SYNTAX  OCTET STRING (SIZE(1..32))
    MAX-ACCESS read-only
    STATUS    current
    DESCRIPTION "Access Point Hardware"
    ::= { apStatsEntry 6 }

apHardwareRev  OBJECT-TYPE
    SYNTAX  OCTET STRING (SIZE(1..6))
    MAX-ACCESS read-only
    STATUS    current
    DESCRIPTION "Access Point Hardware Revision"
    ::= { apStatsEntry 7 }
    
apSerial  OBJECT-TYPE
    SYNTAX  OCTET STRING (SIZE(1..16))
    MAX-ACCESS read-only
    STATUS    current
    DESCRIPTION "Access Point Serial Number"
    ::= { apStatsEntry 8 }

apIp  OBJECT-TYPE
    SYNTAX  IpAddress
    MAX-ACCESS read-only
    STATUS    current
    DESCRIPTION "Access Point IPv4 Address"
    ::= { apStatsEntry 9 }
    
apPublicIp  OBJECT-TYPE
    SYNTAX  IpAddress
    MAX-ACCESS read-only
    STATUS    current
    DESCRIPTION "Access Point IPv4 Address"
    ::= { apStatsEntry 10 }

apClientCount  OBJECT-TYPE
    SYNTAX    Integer32
    MAX-ACCESS read-only
    STATUS    current
    DESCRIPTION
        "Number of connected clients to the 
        Access Point"
    ::= { apStatsEntry 11 }

apLldpSysName OBJECT-TYPE
    SYNTAX  OCTET STRING (SIZE(0..255))
    MAX-ACCESS read-only
    STATUS current
    DESCRIPTION "LLDP Neighbord System Name"
    ::= { apStatsEntry 12 }

apLldpSysDesc OBJECT-TYPE
    SYNTAX  OCTET STRING (SIZE(0..255))
    MAX-ACCESS read-only
    STATUS current
    DESCRIPTION "LLDP Neighbord System Description"
    ::= { apStatsEntry 13 }

apLldpPortId  OBJECT-TYPE
    SYNTAX  OCTET STRING (SIZE(0..255))
    MAX-ACCESS read-only
    STATUS current
    DESCRIPTION "LLDP Neighbord Port Id"
    ::= { apStatsEntry 14 }

apLldpPortDesc  OBJECT-TYPE
    SYNTAX  OCTET STRING (SIZE(0..255))
    MAX-ACCESS read-only
    STATUS current
    DESCRIPTION "LLDP Neighbord Port Description"
    ::= { apStatsEntry 15 }
    
apLldpChassisId  OBJECT-TYPE
    SYNTAX  OCTET STRING (SIZE(0..16))
    MAX-ACCESS read-only
    STATUS current
    DESCRIPTION "LLDP Neighbord Chassis ID"
    ::= { apStatsEntry 16 }

apLldpMed  OBJECT-TYPE
    SYNTAX    INTEGER {
        false (1),
        true (2)
    }
    MAX-ACCESS read-only
    STATUS    current
    DESCRIPTION "LLDP-MED supported by the LLDP Neighbord switch port"
    ::= { apStatsEntry 17 }
    
apPwrReq  OBJECT-TYPE
    SYNTAX  Integer32
    MAX-ACCESS read-only
    STATUS    current
    DESCRIPTION "Power requested by the AP interface"
    ::= { apStatsEntry 18 }

apPwrAlloc  OBJECT-TYPE
    SYNTAX    Integer32
    MAX-ACCESS read-only
    STATUS    current
    DESCRIPTION "Power allocated by the PSE"
    ::= { apStatsEntry 19 }

apPwrDraw  OBJECT-TYPE
    SYNTAX    Integer32
    MAX-ACCESS read-only
    STATUS    current
    DESCRIPTION "Power drawed by the AP interface"
    ::= { apStatsEntry 20 }


--**********************************************************************
-- AP ETH STRUCTURE
--**********************************************************************

apEthTable    OBJECT-TYPE
    SYNTAX SEQUENCE OF ApEthEntry
    MAX-ACCESS not-accessible
    STATUS    current
    DESCRIPTION
        "This is the data structure associated to
        mist access points interfaces table"
    ::= { ap 2 }

apEthEntry    OBJECT-TYPE
    SYNTAX    ApEthEntry
    MAX-ACCESS not-accessible
    STATUS    current
    DESCRIPTION
        "This is the data structure associated to
        mist access points interfaces entry"
    INDEX  { siteId,apMac,apEthPort }
    ::= { apEthTable 1 }

ApEthEntry   ::= SEQUENCE {
    apEthPort           OCTET STRING,
    apEthStatus         INTEGER,
    apEthSpeed          Integer32,
    apEthDuplex         INTEGER,
    apEthTxBytes        OCTET STRING,
    apEthRxBytes        OCTET STRING,
    apEthTxPkts         OCTET STRING,
    apEthRxPkts         OCTET STRING,
    apEthRxErrors       OCTET STRING,
}

apEthPort  OBJECT-TYPE
    SYNTAX  OCTET STRING (SIZE(1..4))
    MAX-ACCESS read-only
    STATUS    current
    DESCRIPTION "AP Interface Name"
    ::= { apEthEntry 1 }

apEthStatus  OBJECT-TYPE
    SYNTAX    INTEGER {
        down (1),
        up (2)
    }
    MAX-ACCESS read-only
    STATUS    current
    DESCRIPTION "AP Inteface Status"
    ::= { apEthEntry 2 }

apEthSpeed  OBJECT-TYPE
    SYNTAX    Integer32 
    MAX-ACCESS read-only
    STATUS    current
    DESCRIPTION "AP Interface Speed"
    ::= { apEthEntry 3 }

apEthDuplex OBJECT-TYPE
    SYNTAX    INTEGER {
        half (1),
        full (2)
    }
    MAX-ACCESS read-only
    STATUS    current
    DESCRIPTION "AP Interface Duplex"
    ::= { apEthEntry 4 }

apEthTxBytes  OBJECT-TYPE
    SYNTAX    OCTET STRING (SIZE(1..14)) 
    MAX-ACCESS read-only
    STATUS    current
    DESCRIPTION "AP Interface Tx Bytes"
    ::= { apEthEntry 5 }

apEthRxBytes  OBJECT-TYPE
    SYNTAX    OCTET STRING (SIZE(1..14)) 
    MAX-ACCESS read-only
    STATUS    current
    DESCRIPTION "AP Interface Rx Bytes"
    ::= { apEthEntry 6 }

apEthTxPkts  OBJECT-TYPE
    SYNTAX    OCTET STRING (SIZE(1..14)) 
    MAX-ACCESS read-only
    STATUS    current
    DESCRIPTION "AP Interface Tx Packets"
    ::= { apEthEntry 7 }

apEthRxPkts  OBJECT-TYPE
    SYNTAX    OCTET STRING (SIZE(1..14)) 
    MAX-ACCESS read-only
    STATUS    current
    DESCRIPTION "AP Interface Rx Packets"
    ::= { apEthEntry 8 }

apEthRxErrors  OBJECT-TYPE
    SYNTAX    OCTET STRING (SIZE(1..14)) 
    MAX-ACCESS read-only
    STATUS    current
    DESCRIPTION "AP Interface Rx Errors"
    ::= { apEthEntry 9 }

--**********************************************************************
-- SWITCH STRUCTURE
--**********************************************************************
switch   OBJECT IDENTIFIER ::= { mistLab 4 }

switchStatsTable    OBJECT-TYPE
    SYNTAX SEQUENCE OF SwitchStatsEntry
    MAX-ACCESS not-accessible
    STATUS    current
    DESCRIPTION
        "This is the data structure associated to
        mist access points status table"
    ::= { switch 1 }

switchStatsEntry    OBJECT-TYPE
    SYNTAX    SwitchStatsEntry
    MAX-ACCESS not-accessible
    STATUS    current
    DESCRIPTION
        "This is the data structure associated to
        mist access points status entry"
    INDEX  { siteId,switchFpc0Mac,switchFpcIdx }
    ::= { switchStatsTable 1 }

SwitchStatsEntry   ::= SEQUENCE {
    switchFpc0Mac           OCTET STRING,
    switchFpcIdx            Integer32,

    switchName              DisplayString,
    switchStatus            INTEGER,
    switchLastSeen          Integer32,
    switchIp                IpAddress,

    switchMac               OCTET STRING,
    switchSerial            OCTET STRING,
    switchVcRole            INTEGER,
    switchModel             OCTET STRING,
    switchUptime            Integer32,
    switchVersion           OCTET STRING,
    switchPoeMax            OCTET STRING,
    switchPoeDraw           OCTET STRING,
    switchFanOStatus        INTEGER,
    switchFan1Status        INTEGER,
    switchTempCpu           Integer32,
    switchTempCpuStatus     INTEGER,
    switchTempPsu           Integer32,
    switchTempPsuStatus     INTEGER,
    switchPsu0Status        INTEGER,
    switchPsu1Status        INTEGER,
    switchCpuLoad1          OCTET STRING,
    switchCpuLoad5          OCTET STRING,
    switchCpuLoad15         OCTET STRING,
    switchMemoryUsage       Integer32
}

switchFpc0Mac  OBJECT-TYPE
    SYNTAX  OCTET STRING (SIZE(1..162))
    MAX-ACCESS read-only
    STATUS    current
    DESCRIPTION
        "Switch/Virtual chassis FPC0 MAC address"
    ::= { switchStatsEntry 1 }

switchFpcIdx OBJECT-TYPE
    SYNTAX    Integer32 (0..10)
    MAX-ACCESS read-only
    STATUS current
    DESCRIPTION "Switch member ID in the Virtual chassis FPC Index"
    ::= { switchStatsEntry 2 }

switchName  OBJECT-TYPE
    SYNTAX  DisplayString  (SIZE(1..255))
    MAX-ACCESS read-only
    STATUS    current
    DESCRIPTION "Switch/Virtual Chassis Name"
    ::= { switchStatsEntry 3 }

switchStatus  OBJECT-TYPE
    SYNTAX    INTEGER {
        disconnected (1),
        connected (2)
    }
    MAX-ACCESS read-only
    STATUS    current
    DESCRIPTION "The connection status of the Switch/Virtual Chassis with the Mist Cloud."
    ::= { switchStatsEntry 4 }

switchLastSeen OBJECT-TYPE
    SYNTAX    Integer32 (1..2147483647)
    MAX-ACCESS read-only
    STATUS current
    DESCRIPTION "The last time the Switch/Virtual Chassis contacted the Mist Cloud"
    ::= { switchStatsEntry 5 }

switchIp  OBJECT-TYPE
    SYNTAX  IpAddress
    MAX-ACCESS read-only
    STATUS    current
    DESCRIPTION "Switch/Virtual Chassis IPv4 Address"
    ::= { switchStatsEntry 6 }




switchMac  OBJECT-TYPE
    SYNTAX  OCTET STRING (SIZE(1..162))
    MAX-ACCESS read-only
    STATUS    current
    DESCRIPTION "Switch/VC Member MAC Address"
    ::= { switchStatsEntry 7 }

switchSerial  OBJECT-TYPE
    SYNTAX  OCTET STRING (SIZE(1..16))
    MAX-ACCESS read-only
    STATUS    current
    DESCRIPTION "Switch Serial Number"
    ::= { switchStatsEntry 8 }

switchVcRole  OBJECT-TYPE
    SYNTAX    INTEGER {
        unknown (1),
        master (2),
        backup (3),
        linecard (4)
    }
    MAX-ACCESS read-only
    STATUS    current
    DESCRIPTION "Switch role in the Virtual Chassis"
    ::= { switchStatsEntry 9 }

switchModel  OBJECT-TYPE
    SYNTAX  OCTET STRING (SIZE(1..32))
    MAX-ACCESS read-only
    STATUS    current
    DESCRIPTION "Model of the switch"
    ::= { switchStatsEntry 10 }

switchUptime OBJECT-TYPE
    SYNTAX    Integer32 (1..2147483647)
    MAX-ACCESS read-only
    STATUS    current
    DESCRIPTION "Switch Uptime"
    ::= { switchStatsEntry 11 }

switchVersion  OBJECT-TYPE
    SYNTAX  OCTET STRING (SIZE(1..32))
    MAX-ACCESS read-only
    STATUS    current
    DESCRIPTION "Running firmware on the switch"
    ::= { switchStatsEntry 12 }
    
switchPoeMax  OBJECT-TYPE
    SYNTAX  OCTET STRING (SIZE(1..32))
    MAX-ACCESS read-only
    STATUS    current
    DESCRIPTION "Chassis PoE budget (in W) "
    ::= { switchStatsEntry 13 }

switchPoeDraw  OBJECT-TYPE
    SYNTAX  OCTET STRING (SIZE(1..32))
    MAX-ACCESS read-only
    STATUS    current
    DESCRIPTION "Current Chassis PoE draw (in W) "
    ::= { switchStatsEntry 14 }

switchFanOStatus OBJECT-TYPE
    SYNTAX    INTEGER {
        unknown (1),
        error (2),
        ok (3)
    }
    MAX-ACCESS read-only
    STATUS    current
    DESCRIPTION "Chassis Fan 0 status"
    ::= { switchStatsEntry 15 }

switchFan1Status OBJECT-TYPE
    SYNTAX    INTEGER {
        unknown (1),
        error (2),
        ok (3)
    }
    MAX-ACCESS read-only
    STATUS    current
    DESCRIPTION "Chassis Fan 1 status"
    ::= { switchStatsEntry 16 }

switchTempCpu OBJECT-TYPE
    SYNTAX    Integer32 (1..200)
    MAX-ACCESS read-only
    STATUS current
    DESCRIPTION "Chassis CPU Temperature (in Celcius)"
    ::= { switchStatsEntry 17 }

switchTempCpuStatus  OBJECT-TYPE
    SYNTAX    INTEGER {
        unknown (1),
        error (2),
        ok (3)
    }
    MAX-ACCESS read-only
    STATUS    current
    DESCRIPTION "Chassis CPU temperature status"
    ::= { switchStatsEntry 18 }

switchTempPsu OBJECT-TYPE
    SYNTAX    Integer32 (1..200)
    MAX-ACCESS read-only
    STATUS current
    DESCRIPTION "Chassis PSU Temperature (in Celcius)"
    ::= { switchStatsEntry 19 }

switchTempPsuStatus  OBJECT-TYPE
    SYNTAX    INTEGER {
        unknown (1),
        error (2),
        ok (3)
    }
    MAX-ACCESS read-only
    STATUS    current
    DESCRIPTION "Chassis PSU temperature status"
    ::= { switchStatsEntry 20 }

switchPsu0Status  OBJECT-TYPE
    SYNTAX    INTEGER {
        unknown (1),
        error (2),
        ok (3)
    }
    MAX-ACCESS read-only
    STATUS    current
    DESCRIPTION "Chassis PSU0 status"
    ::= { switchStatsEntry 21 }

switchPsu1Status  OBJECT-TYPE
    SYNTAX    INTEGER {
        unknown (1),
        error (2),
        ok (3)
    }
    MAX-ACCESS read-only
    STATUS    current
    DESCRIPTION "Chassis PSU1 status"
    ::= { switchStatsEntry 22 }

switchCpuLoad1  OBJECT-TYPE
    SYNTAX  OCTET STRING (SIZE(1..5))
    MAX-ACCESS read-only
    STATUS current
    DESCRIPTION "Switch CPU Load - 1m"
    ::= { switchStatsEntry 23 }
    
switchCpuLoad5  OBJECT-TYPE
    SYNTAX  OCTET STRING (SIZE(1..5))
    MAX-ACCESS read-only
    STATUS current
    DESCRIPTION "Switch CPU Load - 5m"
    ::= { switchStatsEntry 24 }

switchCpuLoad15  OBJECT-TYPE
    SYNTAX  OCTET STRING (SIZE(1..5))
    MAX-ACCESS read-only
    STATUS    current
    DESCRIPTION "Switch CPU Load - 15m"
    ::= { switchStatsEntry 25 }
    
switchMemoryUsage  OBJECT-TYPE
    SYNTAX    Integer32 (1..100)
    MAX-ACCESS read-only
    STATUS    current
    DESCRIPTION
        "Switch Memory usage (%)"
    ::= { switchStatsEntry 26 }

--**********************************************************************
-- SWITCH ETH STRUCTURE
--**********************************************************************

switchEthTable    OBJECT-TYPE
    SYNTAX SEQUENCE OF SwitchEthEntry
    MAX-ACCESS not-accessible
    STATUS    current
    DESCRIPTION
        "This is the data structure associated to
        juniper switches interfaces table"
    ::= { switch 2 }

switchEthEntry    OBJECT-TYPE
    SYNTAX    SwitchEthEntry
    MAX-ACCESS not-accessible
    STATUS    current
    DESCRIPTION
        "This is the data structure associated to
        juniper switches interfaces entry"
    INDEX  { siteId,switchFpc0Mac,switchEthPort }
    ::= { switchEthTable 1 }

SwitchEthEntry   ::= SEQUENCE {
    switchEthPort           OCTET STRING,
    switchEthStatus         INTEGER,
    switchEthTxBytes        OCTET STRING,
    switchEthRxBytes        OCTET STRING,
    switchEthTxPkts         OCTET STRING,
    switchEthRxPkts         OCTET STRING
}

switchEthPort  OBJECT-TYPE
    SYNTAX  OCTET STRING (SIZE(1..10))
    MAX-ACCESS read-only
    STATUS    current
    DESCRIPTION "Switch Interface Name"
    ::= { switchEthEntry 1 }

switchEthStatus  OBJECT-TYPE
    SYNTAX    INTEGER {
        down (1),
        up (2)
    }
    MAX-ACCESS read-only
    STATUS    current
    DESCRIPTION "Switch Inteface Status"
    ::= { switchEthEntry 2 }

switchEthTxBytes  OBJECT-TYPE
    SYNTAX    OCTET STRING (SIZE(1..14)) 
    MAX-ACCESS read-only
    STATUS    current
    DESCRIPTION "Switch Interface Tx Bytes"
    ::= { switchEthEntry 3 }

switchEthRxBytes  OBJECT-TYPE
    SYNTAX    OCTET STRING (SIZE(1..14)) 
    MAX-ACCESS read-only
    STATUS    current
    DESCRIPTION "Switch Interface Rx Bytes"
    ::= { switchEthEntry 4 }

switchEthTxPkts  OBJECT-TYPE
    SYNTAX    OCTET STRING (SIZE(1..14)) 
    MAX-ACCESS read-only
    STATUS    current
    DESCRIPTION "Switch Interface Tx Packets"
    ::= { switchEthEntry 5 }

switchEthRxPkts  OBJECT-TYPE
    SYNTAX    OCTET STRING (SIZE(1..14)) 
    MAX-ACCESS read-only
    STATUS    current
    DESCRIPTION "Switch Interface Rx Packets"
    ::= { switchEthEntry 6 }

END
